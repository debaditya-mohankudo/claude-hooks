package UserPromptSubmitFlow {
    doc /* Sequence-diagram-equivalent for the pre-prompt hook flow.
         * SysML v2 textual notation has no distinct sequence-diagram
         * keyword; ordered actions + succession is the closest fit.
         * Ground truth: hooks/dispatcher.py:_handle_user_prompt_submit()
         * and langchain_learning/session_graph.py:build_session_graph().
         * Correction: the epic named hooks/memory_loader_lc.py (an "LCEL
         * pipeline") but that file does not exist in this repo or on
         * this machine — it belongs to a separate global ~/.claude/
         * memory system. Modeled the real mechanism instead: a LangGraph
         * StateGraph, not LCEL. */

    action def UserPromptSubmitFlow {
        action clientForward {
            doc /* hooks/client.py forwards the hook payload to the FastAPI server. */
        }
        action serverRoute {
            doc /* hooks/server.py routes the POST to the dispatcher. */
        }
        action dispatcherCheckState {
            doc /* dispatcher.py reads existing checkpoint state before invoking the graph. */
        }
        action graphInvoke {
            doc /* session_graph.py:run_session() runs the StateGraph. The
                 * UserPromptSubmit chain is now just: load_turn ->
                 * (load_memories, score_tools) fan-out -> fan-in at
                 * set_prompt_id -> END. The task-context pipeline that once
                 * sat here (load_active_task, load_related_tasks,
                 * summarize_task_context, cwd_domain_detect, log_task_events)
                 * is gone (task:882d67fa and follow-ups) — task-framework
                 * owns active-task context and is asked via tasks__context,
                 * not announced by a parallel pipeline here. */
        }
        action loadVaultContext {
            doc /* dispatcher.py adds vault_context after the graph returns:
                 * _load_vault_context() reads the fixed set of LIFE_OS files
                 * (_LIFE_OS_FILES — currently just dev_personality.md) verbatim,
                 * unscored, falling back to the last cached copy on a transient
                 * read failure. See requirements.sysml
                 * VaultContextTransientReadFailureRequirement. */
        }
        action enforceContextBudget {
            doc /* dispatcher.py trims context to fit the token/char budget. */
        }
        action formatSystemPrompt {
            doc /* dispatcher.py assembles additionalContext text from ctx:
                 * _format_system_prompt() renders the "## Dev personality" block
                 * (from vault_context) above "## Injected memories", then the
                 * scored memories and tool hints. */
        }
        action injectResponse {
            doc /* Response flows server.py -> client.py -> Claude Code, injecting the prompt. */
        }

        first clientForward then serverRoute;
        first serverRoute then dispatcherCheckState;
        first dispatcherCheckState then graphInvoke;
        first graphInvoke then loadVaultContext;
        first loadVaultContext then enforceContextBudget;
        first enforceContextBudget then formatSystemPrompt;
        first formatSystemPrompt then injectResponse;
    }
}
